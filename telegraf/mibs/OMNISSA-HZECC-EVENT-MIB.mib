OMNISSA-HZECC-EVENT-MIB DEFINITIONS ::= BEGIN

IMPORTS
   MODULE-IDENTITY, OBJECT-TYPE, NOTIFICATION-TYPE
        FROM SNMPv2-SMI
   MODULE-COMPLIANCE, OBJECT-GROUP, NOTIFICATION-GROUP
        FROM SNMPv2-CONF
   TEXTUAL-CONVENTION
       FROM SNMPv2-TC
   SnmpAdminString
        FROM SNMP-FRAMEWORK-MIB
   omnissaHzecc
       FROM OMNISSA-ROOT-MIB;

    onsHzeccMIB MODULE-IDENTITY
    LAST-UPDATED "202411180000Z"
    ORGANIZATION "Omnissa, Inc."
    CONTACT-INFO
        "Omnissa, LLC
        590 E Middlefield Road
        Mountain View, CA 94043
        Tel: 1-650-239-7600
        "
    DESCRIPTION
        "This MIB file contains the definition of the SNMP
        interface of Omnissa Horizon Cloud Connector.

        Horizon Cloud Connector is an important product which
        enables subscription license for Horizon on-prem VDI & APPs
        "

    REVISION     "202411180000Z"
    DESCRIPTION
        "Initial revision"

    ::= { omnissaHzecc 1 }

onsHzeccNotifications OBJECT IDENTIFIER ::= { omnissaHzecc 0 }
onsHzeccLifecycleEvents OBJECT IDENTIFIER ::= { omnissaHzecc 4 }
onsHzeccSubscriptionLicenseEvents OBJECT IDENTIFIER ::= { omnissaHzecc 5 }

OmnissaHzeccLifecycleEventType ::= TEXTUAL-CONVENTION
    STATUS     current
    DESCRIPTION
           "The lifecycle event type.
           This trap is sent when a life cycle event occurs.
           Except the failure events all other events are informational only
           The value of the same is defined with codes.

           paired - 1 - Indicates that Cloud Connector is being configured
           or reconfigured by an admin by providing Horizon enterprise pod details.
           This is an information only event.
           For more information refer -
           ----------------------------------------------------------------
           unplug - 2 - Indicates that an admin is deleting
           the Cloud Connector pod and related configuration. This is an
           information only event.
           ----------------------------------------------------------------
           Upgrade Events - Cloud Connector Upgrade is based on Blue Green approach.
           Blue appliance is the existing appliance.
           Green appliance is the target upgraded version appliance
           ----------------------------------------------------------------
           bluepreupgrade - 10 -  Indicates that upgrade
           is about to start. This indicates an admin is initiating
           manual or scheduled upgrade of cloud connector appliance.
           This is an information only event.
           ----------------------------------------------------------------
           bluepostupgradesuccess - 20 - Indicates that upgrade
           has successfully completed. This is an information only event.
           ----------------------------------------------------------------
           bluepostupgradefailure - 21 - Indicates that upgrade
           has failed. Upgrade can be restarted back. An Admin who
           initiates upgrade would need to restart the upgrade.
           This is an information only event.
           ----------------------------------------------------------------
           greenpostupgradesuccess - 30 - Indicates that upgrade
           has successfully completed. This is an information only event.
           ----------------------------------------------------------------
           greenpostupgradefailure - 31 - Indicates that upgrade
           has failed during configuration migration step.
           Upgrade can be restarted back by an Admin.
           This is an information only event.
           ----------------------------------------------------------------
           "
    SYNTAX     INTEGER {
        paired(1),
        unplug(2),
        bluepreupgrade(10),
        bluepostupgradesuccess(20),
        bluepostupgradefailure(21),
        greenpostupgradesuccess(30),
        greenpostupgradefailure(31)
    }

--
-- Object Types
--

onsHzeccLCEventName OBJECT-TYPE
   SYNTAX OmnissaHzeccLifecycleEventType
   MAX-ACCESS accessible-for-notify
   STATUS      current
   DESCRIPTION
   "The life cycle event generated."
   ::= { onsHzeccLifecycleEvents 1 }


onsHzeccSubscriptionLicenseFailStatus OBJECT-TYPE
   SYNTAX SnmpAdminString
   MAX-ACCESS accessible-for-notify
   STATUS      current
   DESCRIPTION
   "Subscription license sync status.
   This trap is sent when a subscription license sync fails.
   Subscription license is synced at minimum every 24 hours
   from Horizon Cloud Control Plane to Horizon on-prem.

   This trap indicates that the license sync failed due to the
   mentioned error code. If you received this event for
   more than one day in a row, please navigate to
   Horizon Admin Console and check for connectivity.
   for more information on error codes.

   Possible values - LicenseFailed_400, LicenseFailed_401.
   The number part is the API response code from horizon enterprise.

   In case issue doesn't resolve after following troubleshooting
   steps mentioned in KB article, please reach to Omnissa support.
   "
   ::= { onsHzeccSubscriptionLicenseEvents 1 }

--
-- Notifications Objects
--

onsHzeccLifecycleEventTrap NOTIFICATION-TYPE
    OBJECTS {
                onsHzeccLCEventName
            }
    STATUS      current
    DESCRIPTION
        "This trap is sent when a life cycle event occurs.
        This is an informational event only. There is no action to take upon receipt.
        Frequency:
        This event is sent once when (some part of your system) receives a configuration update.
        The value of the same is defined with codes.
        "
    ::= { onsHzeccNotifications 1 }

onsHzeccSubscriptionLicenseEventTrap NOTIFICATION-TYPE
    OBJECTS {
                onsHzeccSubscriptionLicenseFailStatus
            }
    STATUS      current
    DESCRIPTION
        "This trap is sent when a subscription license sync fails.
        Subscription license is synced at every 24 hours
        from Horizon Cloud Control Plane to Horizon on-prem.

        This trap indicates that the license sync failed due to the
        mentioned error code. If you received this event for
        more than one day in a row, please navigate to
        Horizon Admin Console and check for connectivity.
        for more information on error codes.

        Frequency: This event is sent when the license sync fails. 
                   After that once every 24 hrs until the issue is resolved

        Possible values - LicenseFailed_400, LicenseFailed_401, LicenseFailed_500 etc.
        The number part is the API response code from horizon enterprise.

        In case issue doesn't resolve after following troubleshooting
        steps mentioned in KB article, please reach to Omnissa support.
        "
    ::= { onsHzeccNotifications 2 }

-- conformance information

onsHzeccMIBConformance OBJECT IDENTIFIER ::= { onsHzeccMIB 1 }
onsHzeccMIBCompliances OBJECT IDENTIFIER ::= { onsHzeccMIBConformance 1 }
onsHzeccMIBGroups OBJECT IDENTIFIER ::= { onsHzeccMIBConformance 2 }

onsHzeccMIBBasicCompliance MODULE-COMPLIANCE
    STATUS     current
    DESCRIPTION
    "The compliance statement for entities which implement OMNISSA-HZECC-EVENT-MIB."
    MODULE -- this module
    MANDATORY-GROUPS { onsHzeccNotificationGroup, onsHzeccObjectGroup }
    ::= { onsHzeccMIBCompliances 1 }

onsHzeccObjectGroup OBJECT-GROUP
    OBJECTS {
        onsHzeccLCEventName,
        onsHzeccSubscriptionLicenseFailStatus
    }
    STATUS current
    DESCRIPTION
    "These objects provide notification details."
    ::= { onsHzeccMIBGroups 1 }

onsHzeccNotificationGroup NOTIFICATION-GROUP
    NOTIFICATIONS {
        onsHzeccLifecycleEventTrap,
        onsHzeccSubscriptionLicenseEventTrap
    }
    STATUS current
    DESCRIPTION
    "Group of objects describing notifications."
    ::= { onsHzeccMIBGroups 2 }

END
